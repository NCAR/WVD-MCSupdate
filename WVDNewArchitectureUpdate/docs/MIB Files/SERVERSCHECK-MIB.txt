SERVERSCHECK-MIB DEFINITIONS ::= BEGIN
    IMPORTS
    enterprises, IpAddress
        FROM RFC1155-SMI
    DisplayString
        FROM RFC1213-MIB
    OBJECT-TYPE
        FROM RFC-1212
    TRAP-TYPE
        FROM RFC-1215;


    serverscheck OBJECT IDENTIFIER ::= { enterprises 17095 }

    product OBJECT IDENTIFIER ::= { serverscheck 1 }

    productname OBJECT-TYPE
        SYNTAX              DisplayString
        ACCESS              read-only
        STATUS              mandatory
        DESCRIPTION         "Name of product. e.g. SensorGateway etc."
        ::= { product 1 }

    productversion OBJECT-TYPE
        SYNTAX              DisplayString
        ACCESS              read-only
        STATUS              mandatory
        DESCRIPTION         "Version of product. e.g. 1.0 etc"
        ::= { product 2 }

    productdate OBJECT-TYPE
        SYNTAX              DisplayString
        ACCESS              read-only
        STATUS              mandatory
        DESCRIPTION         "Build date of product. e.g. Apr 2010 etc"
        ::= { product 3 }

    productusername OBJECT-TYPE
        SYNTAX              DisplayString
        ACCESS              read-only
        STATUS              mandatory
        DESCRIPTION         "User give name of product. e.g. ABCD etc"
        ::= { product 4 }

    productuserloc OBJECT-TYPE
        SYNTAX              DisplayString
        ACCESS              read-only
        STATUS              mandatory
        DESCRIPTION         "Usage loaction of product. e.g. Data center etc"
        ::= { product 5 }

    productnetip OBJECT-TYPE
        SYNTAX              IpAddress
        ACCESS              read-only
        STATUS              mandatory
        DESCRIPTION         "IP Address of product"
        ::= { product 6 }

    productnetgateway OBJECT-TYPE
        SYNTAX              IpAddress
        ACCESS              read-only
        STATUS              mandatory
        DESCRIPTION         "Gateway of product"
        ::= { product 7 }

    productnetpridns OBJECT-TYPE
        SYNTAX              IpAddress
        ACCESS              read-only
        STATUS              mandatory
        DESCRIPTION         "Primary DNS of product"
        ::= { product 8 }

    productnetsecdns OBJECT-TYPE
        SYNTAX              IpAddress
        ACCESS              read-only
        STATUS              mandatory
        DESCRIPTION         "Secondary DNS of product"
        ::= { product 9 }

    setup OBJECT IDENTIFIER ::= { serverscheck 2 }

    traps OBJECT-TYPE
        SYNTAX              SEQUENCE OF TrapEntry
        ACCESS              not-accessible
        STATUS              mandatory
        DESCRIPTION         "Trap table"
        ::= { setup 1 }

    trapEntry OBJECT-TYPE
        SYNTAX              TrapEntry
        ACCESS              not-accessible
        STATUS              mandatory
        DESCRIPTION         "Single trap entry containing trap receiver info."
        INDEX               {
                                trapReceiverNumber
                            }
        ::= { traps 1 }

    TrapEntry ::= SEQUENCE {
        trapReceiverNumber
            INTEGER,
        trapEnabled
            INTEGER,
        trapReceiverIPAddress
            IpAddress,
        trapCommunity
            DisplayString
    }

    trapReceiverNumber OBJECT-TYPE
        SYNTAX              INTEGER (0..3)
        ACCESS              not-accessible
        STATUS              mandatory
        DESCRIPTION         "Index of trap receiver"
        ::= { trapEntry 1 }

    trapEnabled OBJECT-TYPE
        SYNTAX              INTEGER {
                                no( 0 ),
                                yes( 1 )
                            }
        ACCESS              read-write
        STATUS              mandatory
        DESCRIPTION         "Indicates if this trap entry is enabled or not."
        ::= { trapEntry 2 }

    trapReceiverIPAddress OBJECT-TYPE
        SYNTAX              IpAddress
        ACCESS              read-write
        STATUS              mandatory
        DESCRIPTION         "Trap receiver IP address"
        ::= { trapEntry 3 }

    trapCommunity OBJECT-TYPE
        SYNTAX              DisplayString
        ACCESS              read-write
        STATUS              mandatory
        DESCRIPTION         "Trap community to be used by agent to send trap"
        ::= { trapEntry 4 }

    control OBJECT IDENTIFIER ::= { serverscheck 3 }

    sensor1name OBJECT-TYPE
        SYNTAX              DisplayString
        ACCESS              read-only
        STATUS              mandatory
        DESCRIPTION         "Type of Sensor"
        ::= { control 1 }

    sensor1Value OBJECT-TYPE
        SYNTAX              DisplayString
        ACCESS              read-only
        STATUS              mandatory
        DESCRIPTION         "Value of Sensor"
        ::= { control 2 }

    sensor1LastErrMsg OBJECT-TYPE
        SYNTAX              DisplayString
        ACCESS              read-only
        STATUS              mandatory
        DESCRIPTION         "Last error message of Sensor"
        ::= { control 3 }

    sensor1LastErrTime OBJECT-TYPE
        SYNTAX              DisplayString
        ACCESS              read-only
        STATUS              mandatory
        DESCRIPTION         "Last error time of Sensor"
        ::= { control 4 }

    sensor2name OBJECT-TYPE
        SYNTAX              DisplayString
        ACCESS              read-only
        STATUS              mandatory
        DESCRIPTION         "Type of Sensor"
        ::= { control 5 }

    sensor2Value OBJECT-TYPE
        SYNTAX              DisplayString
        ACCESS              read-only
        STATUS              mandatory
        DESCRIPTION         "Value of Sensor"
        ::= { control 6 }

    sensor2LastErrMsg OBJECT-TYPE
        SYNTAX              DisplayString
        ACCESS              read-only
        STATUS              mandatory
        DESCRIPTION         "Last error message of Sensor"
        ::= { control 7 }

    sensor2LastErrTime OBJECT-TYPE
        SYNTAX              DisplayString
        ACCESS              read-only
        STATUS              mandatory
        DESCRIPTION         "Last error time of Sensor"
        ::= { control 8 }

    sensor3name OBJECT-TYPE
        SYNTAX              DisplayString
        ACCESS              read-only
        STATUS              mandatory
        DESCRIPTION         "Type of Sensor"
        ::= { control 9 }

    sensor3Value OBJECT-TYPE
        SYNTAX              DisplayString
        ACCESS              read-only
        STATUS              mandatory
        DESCRIPTION         "Value of Sensor"
        ::= { control 10 }

    sensor3LastErrMsg OBJECT-TYPE
        SYNTAX              DisplayString
        ACCESS              read-only
        STATUS              mandatory
        DESCRIPTION         "Last error message of Sensor"
        ::= { control 11 }

    sensor3LastErrTime OBJECT-TYPE
        SYNTAX              DisplayString
        ACCESS              read-only
        STATUS              mandatory
        DESCRIPTION         "Last error time of Sensor"
        ::= { control 12 }

    sensor4name OBJECT-TYPE
        SYNTAX              DisplayString
        ACCESS              read-only
        STATUS              mandatory
        DESCRIPTION         "Type of Sensor"
        ::= { control 13 }

    sensor4Value OBJECT-TYPE
        SYNTAX              DisplayString
        ACCESS              read-only
        STATUS              mandatory
        DESCRIPTION         "Value of Sensor"
        ::= { control 14 }

    sensor4LastErrMsg OBJECT-TYPE
        SYNTAX              DisplayString
        ACCESS              read-only
        STATUS              mandatory
        DESCRIPTION         "Last error message of Sensor"
        ::= { control 15 }

    sensor4LastErrTime OBJECT-TYPE
        SYNTAX              DisplayString
        ACCESS              read-only
        STATUS              mandatory
        DESCRIPTION         "Last error time of Sensor"
        ::= { control 16 }

    sensor5name OBJECT-TYPE
        SYNTAX              DisplayString
        ACCESS              read-only
        STATUS              mandatory
        DESCRIPTION         "Type of Sensor"
        ::= { control 17 }

    sensor5Value OBJECT-TYPE
        SYNTAX              DisplayString
        ACCESS              read-only
        STATUS              mandatory
        DESCRIPTION         "Value of Sensor"
        ::= { control 18 }

    sensor5LastErrMsg OBJECT-TYPE
        SYNTAX              DisplayString
        ACCESS              read-only
        STATUS              mandatory
        DESCRIPTION         "Last error message of Sensor"
        ::= { control 19 }

    sensor5LastErrTime OBJECT-TYPE
        SYNTAX              DisplayString
        ACCESS              read-only
        STATUS              mandatory
        DESCRIPTION         "Last error time of Sensor"
        ::= { control 20 }

    trapalerts OBJECT IDENTIFIER ::= { serverscheck 4 }

    sensor1TrapErrMsg OBJECT-TYPE
        SYNTAX              OCTET STRING
        ACCESS              read-only
        STATUS              mandatory
        DESCRIPTION         "Latest complete error message of the first sensor
                            reading"
        ::= { trapalerts 1 }

    sensor2TrapErrMsg OBJECT-TYPE
        SYNTAX              OCTET STRING
        ACCESS              read-only
        STATUS              mandatory
        DESCRIPTION         "Latest complete error message of the second sensor
                            reading"
        ::= { trapalerts 2 }

    sensor3TrapErrMsg OBJECT-TYPE
        SYNTAX              OCTET STRING
        ACCESS              read-only
        STATUS              mandatory
        DESCRIPTION         "Latest complete error message of the third sensor
                            reading"
        ::= { trapalerts 3 }

    sensor4TrapErrMsg OBJECT-TYPE
        SYNTAX              OCTET STRING
        ACCESS              read-only
        STATUS              mandatory
        DESCRIPTION         "Latest complete error message of the fourth sensor
                            reading"
        ::= { trapalerts 4 }


    sensor5TrapErrMsg OBJECT-TYPE
        SYNTAX              OCTET STRING
        ACCESS              read-only
        STATUS              mandatory
        DESCRIPTION         "Latest complete error message of the fifth sensor
                            reading"
        ::= { trapalerts 5 }

    sensor6TrapErrMsg OBJECT-TYPE
        SYNTAX              OCTET STRING
        ACCESS              read-only
        STATUS              mandatory
        DESCRIPTION         "Latest complete error message of the sixth sensor
                            reading"
        ::= { trapalerts 4 }

    sensorAlert TRAP-TYPE
        ENTERPRISE          serverscheck
        VARIABLES           {
                                sensor1TrapErrMsg,
                                sensor2TrapErrMsg,
                                sensor3TrapErrMsg,
				sensor4TrapErrMsg,
				sensor5TrapErrMsg,
				sensor6TrapErrMsg
                            }
        DESCRIPTION         "An alert has been triggered by the SensorGateway on
                             one of the connected sensors.  See the detailed error
                             message for information."
        ::= 1



    iotrapalerts OBJECT IDENTIFIER ::= { serverscheck 5 }

    iosensorINPUT1trapErrMsg OBJECT-TYPE
        SYNTAX              OCTET STRING
        ACCESS              read-only
        STATUS              mandatory
        DESCRIPTION         "Latest complete error message of dry contact input 1"
        ::= { iotrapalerts 1 }

    iosensorINPUT2trapErrMsg OBJECT-TYPE
        SYNTAX              OCTET STRING
        ACCESS              read-only
        STATUS              mandatory
        DESCRIPTION         "Latest complete error message of dry contact input 2"
        ::= { iotrapalerts 2 }

    iosensorINPUT3trapErrMsg OBJECT-TYPE
        SYNTAX              OCTET STRING
        ACCESS              read-only
        STATUS              mandatory
        DESCRIPTION         "Latest complete error message of dry contact input 3"
        ::= { iotrapalerts 3 }

    iosensorINPUT4trapErrMsg OBJECT-TYPE
        SYNTAX              OCTET STRING
        ACCESS              read-only
        STATUS              mandatory
        DESCRIPTION         "Latest complete error message of dry contact input 4"
        ::= { iotrapalerts 4 }

    iosensorINPUT5trapErrMsg OBJECT-TYPE
        SYNTAX              OCTET STRING
        ACCESS              read-only
        STATUS              mandatory
        DESCRIPTION         "Latest complete error message of dry contact input 5"
        ::= { iotrapalerts 5 }

    iosensorINPUT6trapErrMsg OBJECT-TYPE
        SYNTAX              OCTET STRING
        ACCESS              read-only
        STATUS              mandatory
        DESCRIPTION         "Latest complete error message of dry contact input 6"
        ::= { iotrapalerts 6 }

    iosensorINPUT7trapErrMsg OBJECT-TYPE
        SYNTAX              OCTET STRING
        ACCESS              read-only
        STATUS              mandatory
        DESCRIPTION         "Latest complete error message of dry contact input 7"
        ::= { iotrapalerts 7 }

    iosensorINPUT8trapErrMsg OBJECT-TYPE
        SYNTAX              OCTET STRING
        ACCESS              read-only
        STATUS              mandatory
        DESCRIPTION         "Latest complete error message of dry contact input 8"
        ::= { iotrapalerts 8 }

    iosensorINPUT9trapErrMsg OBJECT-TYPE
        SYNTAX              OCTET STRING
        ACCESS              read-only
        STATUS              mandatory
        DESCRIPTION         "Latest complete error message of dry contact input 9"
        ::= { iotrapalerts 9 }

    iosensorINPUT10trapErrMsg OBJECT-TYPE
        SYNTAX              OCTET STRING
        ACCESS              read-only
        STATUS              mandatory
        DESCRIPTION         "Latest complete error message of dry contact input 10"
        ::= { iotrapalerts 10 }

    iosensorINPUT11trapErrMsg OBJECT-TYPE
        SYNTAX              OCTET STRING
        ACCESS              read-only
        STATUS              mandatory
        DESCRIPTION         "Latest complete error message of dry contact input 11"
        ::= { iotrapalerts 11 }

    iosensorINPUT12trapErrMsg OBJECT-TYPE
        SYNTAX              OCTET STRING
        ACCESS              read-only
        STATUS              mandatory
        DESCRIPTION         "Latest complete error message of dry contact input 12"
        ::= { iotrapalerts 12 }

    iosensorINPUT13trapErrMsg OBJECT-TYPE
        SYNTAX              OCTET STRING
        ACCESS              read-only
        STATUS              mandatory
        DESCRIPTION         "Latest complete error message of dry contact input 13"
        ::= { iotrapalerts 13 }

    iosensorINPUT14trapErrMsg OBJECT-TYPE
        SYNTAX              OCTET STRING
        ACCESS              read-only
        STATUS              mandatory
        DESCRIPTION         "Latest complete error message of dry contact input 14"
        ::= { iotrapalerts 14 }

    iosensorINPUT15trapErrMsg OBJECT-TYPE
        SYNTAX              OCTET STRING
        ACCESS              read-only
        STATUS              mandatory
        DESCRIPTION         "Latest complete error message of dry contact input 15"
        ::= { iotrapalerts 15 }

    iosensorINPUT16trapErrMsg OBJECT-TYPE
        SYNTAX              OCTET STRING
        ACCESS              read-only
        STATUS              mandatory
        DESCRIPTION         "Latest complete error message of dry contact input 16"
        ::= { iotrapalerts 16 }


    iosensorAlert TRAP-TYPE
        ENTERPRISE          serverscheck
        VARIABLES           {
                                iosensorINPUT1trapErrMsg,
                                iosensorINPUT2trapErrMsg,
                                iosensorINPUT3trapErrMsg,
				iosensorINPUT4trapErrMsg,
				iosensorINPUT5trapErrMsg,
				iosensorINPUT6trapErrMsg,
                                iosensorINPUT7trapErrMsg,
                                iosensorINPUT8trapErrMsg,
				iosensorINPUT9trapErrMsg,
				iosensorINPUT10trapErrMsg,
				iosensorINPUT11trapErrMsg,
                                iosensorINPUT12trapErrMsg,
                                iosensorINPUT13trapErrMsg,
				iosensorINPUT14trapErrMsg,
				iosensorINPUT15trapErrMsg,
				iosensorINPUT16trapErrMsg
                            }
        DESCRIPTION         "An alert has been triggered by the SensorGateway on
                             one of the connected sensors.  See the detailed error
                             message for information."
        ::= 0



    input OBJECT IDENTIFIER ::= { serverscheck 6 }

    input1name OBJECT-TYPE
        SYNTAX              DisplayString
        ACCESS              read-only
        STATUS              mandatory
        DESCRIPTION         "Name"
        ::= { input 1 }

    input1Value OBJECT-TYPE
        SYNTAX              DisplayString
        ACCESS              read-only
        STATUS              mandatory
        DESCRIPTION         "State - O for Open and 1 for Close"
        ::= { input 2 }

    input1LastErrMsg OBJECT-TYPE
        SYNTAX              DisplayString
        ACCESS              read-only
        STATUS              mandatory
        DESCRIPTION         "Last error message of input"
        ::= { input 3 }

    input2name OBJECT-TYPE
        SYNTAX              DisplayString
        ACCESS              read-only
        STATUS              mandatory
        DESCRIPTION         "Name"
        ::= { input 4 }

    input2Value OBJECT-TYPE
        SYNTAX              DisplayString
        ACCESS              read-only
        STATUS              mandatory
        DESCRIPTION         "State - O for Open and 1 for Close"
        ::= { input 5 }

    input2LastErrMsg OBJECT-TYPE
        SYNTAX              DisplayString
        ACCESS              read-only
        STATUS              mandatory
        DESCRIPTION         "Last error message of input"
        ::= { input 6 }

    input3name OBJECT-TYPE
        SYNTAX              DisplayString
        ACCESS              read-only
        STATUS              mandatory
        DESCRIPTION         "Name"
        ::= { input 7 }

    input3Value OBJECT-TYPE
        SYNTAX              DisplayString
        ACCESS              read-only
        STATUS              mandatory
        DESCRIPTION         "State - O for Open and 1 for Close"
        ::= { input 8 }

    input3LastErrMsg OBJECT-TYPE
        SYNTAX              DisplayString
        ACCESS              read-only
        STATUS              mandatory
        DESCRIPTION         "Last error message of input"
        ::= { input 9 }

    input4name OBJECT-TYPE
        SYNTAX              DisplayString
        ACCESS              read-only
        STATUS              mandatory
        DESCRIPTION         "Name"
        ::= { input 10 }

    input4Value OBJECT-TYPE
        SYNTAX              DisplayString
        ACCESS              read-only
        STATUS              mandatory
        DESCRIPTION         "State - O for Open and 1 for Close"
        ::= { input 11 }

    input4LastErrMsg OBJECT-TYPE
        SYNTAX              DisplayString
        ACCESS              read-only
        STATUS              mandatory
        DESCRIPTION         "Last error message of input"
        ::= { input 12 }

    input5name OBJECT-TYPE
        SYNTAX              DisplayString
        ACCESS              read-only
        STATUS              mandatory
        DESCRIPTION         "Name"
        ::= { input 13 }

    input5Value OBJECT-TYPE
        SYNTAX              DisplayString
        ACCESS              read-only
        STATUS              mandatory
        DESCRIPTION         "State - O for Open and 1 for Close"
        ::= { input 14 }

    input5LastErrMsg OBJECT-TYPE
        SYNTAX              DisplayString
        ACCESS              read-only
        STATUS              mandatory
        DESCRIPTION         "Last error message of input"
        ::= { input 15 }

    input6name OBJECT-TYPE
        SYNTAX              DisplayString
        ACCESS              read-only
        STATUS              mandatory
        DESCRIPTION         "Name"
        ::= { input 16 }

    input6Value OBJECT-TYPE
        SYNTAX              DisplayString
        ACCESS              read-only
        STATUS              mandatory
        DESCRIPTION         "State - O for Open and 1 for Close"
        ::= { input 17 }

    input6LastErrMsg OBJECT-TYPE
        SYNTAX              DisplayString
        ACCESS              read-only
        STATUS              mandatory
        DESCRIPTION         "Last error message of input"
        ::= { input 18 }

    input7name OBJECT-TYPE
        SYNTAX              DisplayString
        ACCESS              read-only
        STATUS              mandatory
        DESCRIPTION         "Name"
        ::= { input 19 }

    input7Value OBJECT-TYPE
        SYNTAX              DisplayString
        ACCESS              read-only
        STATUS              mandatory
        DESCRIPTION         "State - O for Open and 1 for Close"
        ::= { input 20 }

    input7LastErrMsg OBJECT-TYPE
        SYNTAX              DisplayString
        ACCESS              read-only
        STATUS              mandatory
        DESCRIPTION         "Last error message of input"
	::= { input 21 }

    input8name OBJECT-TYPE
        SYNTAX              DisplayString
        ACCESS              read-only
        STATUS              mandatory
        DESCRIPTION         "Name"
        ::= { input 22 }

    input8Value OBJECT-TYPE
        SYNTAX              DisplayString
        ACCESS              read-only
        STATUS              mandatory
        DESCRIPTION         "State - O for Open and 1 for Close"
        ::= { input 23 }

    input8LastErrMsg OBJECT-TYPE
        SYNTAX              DisplayString
        ACCESS              read-only
        STATUS              mandatory
        DESCRIPTION         "Last error message of input"
        ::= { input 24 }

    input9name OBJECT-TYPE
        SYNTAX              DisplayString
        ACCESS              read-only
        STATUS              mandatory
        DESCRIPTION         "Name"
        ::= { input 25 }

    input9Value OBJECT-TYPE
        SYNTAX              DisplayString
        ACCESS              read-only
        STATUS              mandatory
        DESCRIPTION         "State - O for Open and 1 for Close"
        ::= { input 26 }

    input9LastErrMsg OBJECT-TYPE
        SYNTAX              DisplayString
        ACCESS              read-only
        STATUS              mandatory
        DESCRIPTION         "Last error message of input"
        ::= { input 27 }

    input10name OBJECT-TYPE
        SYNTAX              DisplayString
        ACCESS              read-only
        STATUS              mandatory
        DESCRIPTION         "Name"
        ::= { input 28 }

    input10Value OBJECT-TYPE
        SYNTAX              DisplayString
        ACCESS              read-only
        STATUS              mandatory
        DESCRIPTION         "State - O for Open and 1 for Close"
        ::= { input 29 }

    input10LastErrMsg OBJECT-TYPE
        SYNTAX              DisplayString
        ACCESS              read-only
        STATUS              mandatory
        DESCRIPTION         "Last error message of input"
        ::= { input 30 }

    input11name OBJECT-TYPE
        SYNTAX              DisplayString
        ACCESS              read-only
        STATUS              mandatory
        DESCRIPTION         "Name"
        ::= { input 31 }

    input11Value OBJECT-TYPE
        SYNTAX              DisplayString
        ACCESS              read-only
        STATUS              mandatory
        DESCRIPTION         "State - O for Open and 1 for Close"
        ::= { input 32 }

    input11LastErrMsg OBJECT-TYPE
        SYNTAX              DisplayString
        ACCESS              read-only
        STATUS              mandatory
        DESCRIPTION         "Last error message of input"
        ::= { input 33 }

    input12name OBJECT-TYPE
        SYNTAX              DisplayString
        ACCESS              read-only
        STATUS              mandatory
        DESCRIPTION         "Name"
        ::= { input 34 }

    input12Value OBJECT-TYPE
        SYNTAX              DisplayString
        ACCESS              read-only
        STATUS              mandatory
        DESCRIPTION         "State - O for Open and 1 for Close"
        ::= { input 35 }

    input12LastErrMsg OBJECT-TYPE
        SYNTAX              DisplayString
        ACCESS              read-only
        STATUS              mandatory
        DESCRIPTION         "Last error message of input"
        ::= { input 36 }


    input13name OBJECT-TYPE
        SYNTAX              DisplayString
        ACCESS              read-only
        STATUS              mandatory
        DESCRIPTION         "Name"
        ::= { input 37 }

    input13Value OBJECT-TYPE
        SYNTAX              DisplayString
        ACCESS              read-only
        STATUS              mandatory
        DESCRIPTION         "State - O for Open and 1 for Close"
        ::= { input 38 }

    input13LastErrMsg OBJECT-TYPE
        SYNTAX              DisplayString
        ACCESS              read-only
        STATUS              mandatory
        DESCRIPTION         "Last error message of input"
        ::= { input 39 }


    input14name OBJECT-TYPE
        SYNTAX              DisplayString
        ACCESS              read-only
        STATUS              mandatory
        DESCRIPTION         "Name"
        ::= { input 40 }

    input14Value OBJECT-TYPE
        SYNTAX              DisplayString
        ACCESS              read-only
        STATUS              mandatory
        DESCRIPTION         "State - O for Open and 1 for Close"
        ::= { input 41 }

    input14LastErrMsg OBJECT-TYPE
        SYNTAX              DisplayString
        ACCESS              read-only
        STATUS              mandatory
        DESCRIPTION         "Last error message of input"
        ::= { input 42 }

    input15name OBJECT-TYPE
        SYNTAX              DisplayString
        ACCESS              read-only
        STATUS              mandatory
        DESCRIPTION         "Name"
        ::= { input 43 }

    input15Value OBJECT-TYPE
        SYNTAX              DisplayString
        ACCESS              read-only
        STATUS              mandatory
        DESCRIPTION         "State - O for Open and 1 for Close"
        ::= { input 44 }

    input15LastErrMsg OBJECT-TYPE
        SYNTAX              DisplayString
        ACCESS              read-only
        STATUS              mandatory
        DESCRIPTION         "Last error message of input"
        ::= { input 45 }

    input16name OBJECT-TYPE
        SYNTAX              DisplayString
        ACCESS              read-only
        STATUS              mandatory
        DESCRIPTION         "Name"
        ::= { input 46 }

    input16Value OBJECT-TYPE
        SYNTAX              DisplayString
        ACCESS              read-only
        STATUS              mandatory
        DESCRIPTION         "State - O for Open and 1 for Close"
        ::= { input 47 }

    input16LastErrMsg OBJECT-TYPE
        SYNTAX              DisplayString
        ACCESS              read-only
        STATUS              mandatory
        DESCRIPTION         "Last error message of input"
        ::= { input 48 }

    output OBJECT IDENTIFIER ::= { serverscheck 7 }

    output1State OBJECT-TYPE
        SYNTAX              DisplayString
        ACCESS              read-only
        STATUS              mandatory
        DESCRIPTION         "State - O for Open and 1 for Close"
        ::= { output 1 }

    output2State OBJECT-TYPE
        SYNTAX              DisplayString
        ACCESS              read-only
        STATUS              mandatory
        DESCRIPTION         "State - O for Open and 1 for Close"
        ::= { output  2 }

    output3State OBJECT-TYPE
        SYNTAX              DisplayString
        ACCESS              read-only
        STATUS              mandatory
        DESCRIPTION         "State - O for Open and 1 for Close"
        ::= { output  3 }

    output4State OBJECT-TYPE
        SYNTAX              DisplayString
        ACCESS              read-only
        STATUS              mandatory
        DESCRIPTION         "State - O for Open and 1 for Close"
        ::= { output  4 }


END
